--- $Id: trackmgr.asn 411759 2013-08-30 18:46:10Z rafanovi $
---
--- Definitions for the TrackManager service
---

NCBI-TrackManager DEFINITIONS ::=
BEGIN

EXPORTS TMgr-Request, TMgr-Reply, TMgr-GenomeContext,
        TMgr-ClientInfo, TMgr-DisplayTrackRequest,
        TMgr-DisplayTrackReply, TMgr-AssemblySpec,TMgr-AttrSpec,
        TMgr-BlastRIDDetail, TMgr-Assembly, TMgr-Attribute, TMgr-DisplayTrack,
        TMgr-DatasetItem, TMgr-DisplayTrackChoice,
        TMgr-CreateUserTrackRequest, TMgr-CreateUserTrackReply,
        TMgr-TrackAttrValueRequest, TMgr-TrackAttrValueReply,
        TMgr-AttrRequest, TMgr-AttrReply, TMgr-ValueRequest, TMgr-AttrValueReply,
        TMgr-TrackAttributes, TMgr-MessageLevel, TMgr-Message;

IMPORTS Seq-id FROM NCBI-Seqloc
        Dbtag FROM NCBI-General;
---
--- Top-level request/reply
---
TMgr-Request ::= CHOICE {
    display-tracks TMgr-DisplayTrackRequest,
    switch-display-tracks TMgr-SwitchTrackContextRequest,
    track-attr-values TMgr-TrackAttrValueRequest,
    blast-tracks TMgr-BlastRIDRequest,
    create-user-tracks TMgr-CreateUserTrackRequest,
    resolve-track-items TMgr-ItemResolverRequest,
    remove-user-tracks TMgr-RemoveUserTrackRequest
}

TMgr-Reply ::= CHOICE {
    display-tracks TMgr-DisplayTrackReply,
    switch-display-tracks TMgr-SwitchTrackContextReply,
    track-attr-values TMgr-TrackAttrValueReply,
    blast-tracks TMgr-BlastRIDReply,
    create-user-tracks TMgr-CreateUserTrackReply,
    resolve-track-items TMgr-ItemResolverReply,
    remove-user-tracks TMgr-RemoveUserTrackReply
}

TMgr-GenomeContext ::= CHOICE {
    assembly TMgr-AssemblySpec,
    sequence Seq-id,
    refseqgene NULL
}

TMgr-ClientInfo ::= SEQUENCE {
    client-name VisibleString,
    context VisibleString OPTIONAL,
    inhouse BOOLEAN DEFAULT FALSE
    --permission keys etc
}

TMgr-TrackACL-Authorization ::= SEQUENCE {
    access-level TMgr-ACL-AccessLevel OPTIONAL,
    access-key VisibleString OPTIONAL
}

TMgr-DisplayTrackRequest ::= SEQUENCE {
    client TMgr-ClientInfo,
    genome-context TMgr-GenomeContext,
    attrs SET OF TMgr-AttrSpec OPTIONAL,
    identity TMgr-Identity OPTIONAL,
    authorization TMgr-TrackACL-Authorization OPTIONAL
}

TMgr-DisplayTrackReply ::= SEQUENCE {
    messages SEQUENCE OF TMgr-Message OPTIONAL,
    display-tracks SET OF TMgr-DisplayTrack OPTIONAL,
    blast-tracks SET OF TMgr-BlastRIDDetail OPTIONAL
    --tracks TMgr-DisplayTracks OPTIONAL
}

TMgr-DTrackId ::= Dbtag

TMgr-SwitchTrackContextRequest ::= SEQUENCE {
    client TMgr-ClientInfo,
    new-genome-context TMgr-GenomeContext,
    current-dtrack-ids SET OF TMgr-DTrackId
}

TMgr-SwitchTrackContextReply ::= SEQUENCE {
    messages SET OF TMgr-Message OPTIONAL,
    display-tracks SET OF TMgr-DisplayTrackChoice OPTIONAL
}

TMgr-TrackAttrValueRequest ::= SEQUENCE {
    track-type-list NULL OPTIONAL,          -- request all track type names
    attr-list TMgr-AttrRequest OPTIONAL,    -- request attributes associated
                                            -- with all or some track types
    value-list TMgr-ValueRequest OPTIONAL   -- request values associated with
                                            -- attribute list
}

TMgr-AttrRequest ::= CHOICE {
    all-attrs NULL,                         -- request all attributes
    track-type-list SET OF VisibleString    -- request attributes associated
                                            -- with track types in list
}

TMgr-ValueRequest ::= SET OF VisibleString  -- list of attributes to return
                                            -- values for

TMgr-TrackAttrValueReply ::= SEQUENCE {
    track-type-list SET OF VisibleString OPTIONAL,   -- list of track types
    attr-list TMgr-AttrReply OPTIONAL,
    value-list SET OF TMgr-AttrValueReply OPTIONAL
}

TMgr-AttrReply ::= CHOICE {
    all-attrs SET OF VisibleString,             -- list of attributes
    track-attr-list SET OF TMgr-TrackAttributes
}

TMgr-TrackAttributes ::= SEQUENCE {
    track-name VisibleString,        -- track type name
    attributes SET OF VisibleString  -- list of attributes associated with track type name
}

TMgr-AttrValueReply ::= SEQUENCE {
    attr-name VisibleString,
    value-list SET OF VisibleString
}

TMgr-SwitchTrackExceptionCode ::= INTEGER {
    track-not-found (0), -- corresponding track not found in new genome context
    other (255)
}

TMgr-SwitchTrackException ::= SEQUENCE {
    dtrack-id TMgr-DTrackId,
    code TMgr-SwitchTrackExceptionCode OPTIONAL
}

TMgr-AssemblySpec ::= CHOICE {
    name SEQUENCE {
        tax-id INTEGER,
        name VisibleString
    },
    accession VisibleString
}

TMgr-AttrSpec ::= SEQUENCE {
    key VisibleString,
    value UTF8String
}

TMgr-Assembly ::= SEQUENCE {
    accession VisibleString,
    name UTF8String,
    short-name UTF8String OPTIONAL,
    description UTF8String OPTIONAL,
    is-complete BOOLEAN OPTIONAL
}

TMgr-Attribute ::= SEQUENCE {
    key VisibleString,
    value UTF8String
}

TMgr-DisplayTrack ::= SEQUENCE {
    dtrack-id TMgr-DTrackId,
    name UTF8String,
    attrs SET OF TMgr-Attribute OPTIONAL
}

TMgr-DatasetItem ::= SEQUENCE {
    name UTF8String,
    attrs SET OF TMgr-Attribute OPTIONAL
}

TMgr-DisplayTrackChoice ::= CHOICE {
    track TMgr-DisplayTrack,
    switch-exception TMgr-SwitchTrackException
}

TMgr-MessageLevel ::= INTEGER {
    warning (0),
    error (1),
    info (2),
    diagnostic (3)
}

TMgr-Message ::= SEQUENCE {
    level TMgr-MessageLevel,
    message VisibleString
}

TMgr-BlastRIDRequest ::= SEQUENCE {
    rid VisibleString
}

TMgr-BlastQuerySeq ::= SEQUENCE {
    query-number INTEGER,
    label VisibleString -- accession or seq-id string
}

TMgr-BlastRIDDetail ::= SEQUENCE {
    rid VisibleString,
    title VisibleString OPTIONAL,
    query-sequences SEQUENCE OF TMgr-BlastQuerySeq OPTIONAL
}

TMgr-BlastRIDReply ::= SEQUENCE {
    messages SEQUENCE OF TMgr-Message OPTIONAL,
    rid-detail TMgr-BlastRIDDetail OPTIONAL
}

TMgr-CreateUserDataItem ::= SEQUENCE {
    datakey VisibleString,
    seqids SET OF VisibleString,
    attrs SET OF TMgr-Attribute OPTIONAL
}

TMgr-IdentityId ::= SEQUENCE {
    id VisibleString,
    id-type TMgr-IdentityIdType
}

TMgr-IdentityIdType ::= INTEGER {
    myncbi-id (0),
    ncbi-sid (1)
}

TMgr-Identity ::= SEQUENCE {
    ids SET OF TMgr-IdentityId
}

TMgr-ACL-AccessLevel ::= INTEGER {
    public (0),
    private (1),
    ncbi (2),
    nih (3)
}

TMgr-TrackACL-Permission ::= SEQUENCE {
    access-level TMgr-ACL-AccessLevel DEFAULT public,
    access-key VisibleString OPTIONAL
}

TMgr-CreateUserTrackRequest ::= SEQUENCE {
    identity TMgr-Identity,
    track-name VisibleString OPTIONAL, -- User-provided track name
    track-descr VisibleString OPTIONAL, -- User-provided data description
    assembly-acc VisibleString OPTIONAL,
    attrs SET OF TMgr-Attribute OPTIONAL,
    data-items SET OF TMgr-CreateUserDataItem,
    access-perms TMgr-TrackACL-Permission
}

TMgr-CreateUserTrackReply ::= SEQUENCE {
    messages SEQUENCE OF TMgr-Message OPTIONAL,
    display-tracks SET OF TMgr-DisplayTrack OPTIONAL
}

TMgr-RemoveUserTrackRequest ::= SEQUENCE {
    identity TMgr-Identity,
    dtrack-ids SET OF TMgr-DTrackId
}

TMgr-RemoveUserTrackReply ::= SEQUENCE {
    messages SEQUENCE OF TMgr-Message OPTIONAL
}

TMgr-ItemResolverRequest ::= SEQUENCE {
    dtrack-ids SET OF TMgr-DTrackId,
    client TMgr-ClientInfo,
    genome-context TMgr-GenomeContext,
    attrs SET OF TMgr-AttrSpec OPTIONAL,
    sequence Seq-id OPTIONAL -- resolve specifically for this top-level sequence
}

TMgr-TrackItems ::= SEQUENCE {
    dtrack-id TMgr-DTrackId,
    data SET OF TMgr-DatasetItem
}

TMgr-ItemResolverReply ::= SEQUENCE {
    messages SEQUENCE OF TMgr-Message OPTIONAL,
    track-items SET OF TMgr-TrackItems OPTIONAL
}


END

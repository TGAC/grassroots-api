-- $Id: gencoll_client.asn 418594 2013-11-18 19:59:52Z rafanovi $
-- **********************************************************************
--
--  NCBI Genome Collections Statistics
--  by Michael DiCuccio, Vinay Kumar
--
-- **********************************************************************




NCBI-GencollClient DEFINITIONS ::=
BEGIN

IMPORTS GC-Assembly FROM NCBI-GenomeCollection;


GCClientRequest ::= CHOICE {
    get-assembly GCClient-GetAssemblyRequest,
    get-chrtype-valid  GCClient-ValidateChrTypeLocRequest
}


GCClientResponse ::= CHOICE {
    get-assembly GC-Assembly,
    get-chrtype-valid  VisibleString,
    
    --  errors encountered at the server side.
    srvr-error GCClient-Error
}

GCClient-Error ::= SEQUENCE {
    error-id INTEGER {
        assembly-not-found(0),
        other(255)
    },
    description VisibleString OPTIONAL
}

-- This is a bitfield.  All values are powers of two.
GCClient-AttributeFlags ::= INTEGER {
    none(0),
    biosource(1),
    -- obsolete; do not use
    molinfo(2),
    -- obsolete; do not use
    publications(4),

-- scaffold-flags:
-- by default, pseudo-scaffolds are reported as submitted.
-- include_unordered_scaffolds: show pseudo-scaffolds as unordered/unplaced
-- include_UCSC_pseudo_scaffolds: all unordered/unplaced aer shown as placed
--  (using UCSC coordinates of chr*_random or chrUn)
    include-unordered-scaffolds (1024), --  1<<10
    include-UCSC-pseudo-scaffolds (2048), -- 1<<11

-- chromosome-flags:
-- by default, alt-loci/patches position on chromosome reported using AlignDb
-- database alignments.
-- exclude_aligndb: report alt-loci/patches position on chromosome
-- using placement and not using AlignDb alignments
    exclude-aligndb (8192) -- 1<<13

}


GCClient-GetAssemblyRequest ::= SEQUENCE {

    -- One of accession or release id MUST BE SUPPLIED
    
    -- Assembly accession or accession.version
    -- (versionless accession is answered with most recent version)
    accession VisibleString OPTIONAL,

    -- release ID
    release-id INTEGER OPTIONAL,

    level INTEGER {
        assembly(0),
        replicon(1),
        scaffold(2),
        component(3)
    } DEFAULT scaffold,

    -- assm-flags, chrom-flags, scaf-flags, component-flags
    assm-flags GCClient-AttributeFlags DEFAULT none,

    chrom-flags GCClient-AttributeFlags DEFAULT biosource,
    
    scaf-flags GCClient-AttributeFlags DEFAULT none,
    
    component-flags GCClient-AttributeFlags DEFAULT none
}

GCClient-ValidateChrTypeLocRequest ::= SEQUENCE {
    
    -- Validate the Type Location in the request
    
    type  VisibleString,
    
    location VisibleString
}

GCClient-ValidateChrTypeLocResponse ::= SEQUENCE {
    
    -- Result of the Type Location validate request
    
    result  VisibleString
}



END
